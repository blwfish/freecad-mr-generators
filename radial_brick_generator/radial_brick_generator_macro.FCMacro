"""
Parametric Radial Brick Generator for FreeCAD v2.0.0

Fully parametric: change BrickLength, BrickHeight, MaterialThickness, or
MortarThickness in the Properties panel and the brick skin regenerates.

Generates running-bond brick patterns on cylindrical and conical surfaces.
Primary use cases: smokestacks, water towers, silos, grain elevators.

WORKFLOW:
1. Select one or more cylindrical or conical faces
2. Run this macro
3. RadialBrickWall appears — adjust properties in panel

Version History:
- 2.0.0: FeaturePython conversion — fully parametric live-update object.
         Generation logic moved to radial_brick_proxy.py.
- 1.1.0: Transaction wrapping for undo
- 1.0.0: Initial release
"""

import FreeCAD as App
import FreeCADGui as Gui
import sys

from radial_brick_proxy import RadialBrickProxy, RadialBrickViewProxy, VERSION


def main():
    sel = Gui.Selection.getSelectionEx()
    if not sel:
        App.Console.PrintError(
            "Nothing selected — please select one or more cylindrical/conical faces.\n")
        return

    link_sub = []
    for sel_obj in sel:
        if not sel_obj.HasSubObjects:
            App.Console.PrintWarning(f"  {sel_obj.Object.Label}: select a face\n")
            continue
        face_names = [s for s in sel_obj.SubElementNames if s.startswith("Face")]
        if face_names:
            link_sub.append((sel_obj.Object, tuple(face_names)))

    if not link_sub:
        App.Console.PrintError("No faces in selection.\n")
        return

    total = sum(len(n) for _, n in link_sub)
    App.Console.PrintMessage(f"Radial Brick v{VERSION}: {total} face(s) selected\n")

    doc = App.ActiveDocument or App.newDocument()

    doc.openTransaction("radial_brick_generator: RadialBrickWall")
    try:
        obj = doc.addObject("Part::FeaturePython", "RadialBrickWall")
        RadialBrickProxy(obj)
        RadialBrickViewProxy(obj.ViewObject)
        RadialBrickProxy.set_defaults(obj)
        obj.Sources = link_sub
        obj.ViewObject.ShapeColor = (0.72, 0.48, 0.38)
        doc.recompute()
        doc.commitTransaction()
    except Exception:
        doc.abortTransaction()
        raise

    App.Console.PrintMessage(
        f"\n✓ Parametric RadialBrickWall created.\n"
        f"  Edit BrickLength, BrickHeight, MaterialThickness, MortarThickness\n"
        f"  in the Properties panel.\n\n")


if __name__ == '__main__':
    main()
