"""
Parametric Bead Board Trim Generator for FreeCAD v2.0.1

Fully parametric: change BeadSpacing, BeadDepth, or BeadGap in the Properties
panel and the bead board trim regenerates.

WORKFLOW:
1. Select one or more wall faces
2. Run this macro
3. BeadBoardWall appears — adjust properties in panel

Version History:
- 2.0.0: FeaturePython conversion — fully parametric live-update object.
         Generation logic moved to bead_board_proxy.py.
- 1.1.0: Transaction wrapping for undo
- 1.0.0: Initial release
"""

import FreeCAD as App
import FreeCADGui as Gui
import sys

from bead_board_proxy import BeadBoardProxy, BeadBoardViewProxy, VERSION


def main():
    sel = Gui.Selection.getSelectionEx()
    if not sel:
        App.Console.PrintError("Nothing selected — please select one or more wall faces.\n")
        return

    link_sub = []
    for sel_obj in sel:
        if not sel_obj.HasSubObjects:
            App.Console.PrintWarning(f"  {sel_obj.Object.Label}: select a face\n")
            continue
        face_names = [s for s in sel_obj.SubElementNames if s.startswith("Face")]
        if face_names:
            link_sub.append((sel_obj.Object, tuple(face_names)))

    if not link_sub:
        App.Console.PrintError("No faces in selection.\n")
        return

    total = sum(len(n) for _, n in link_sub)
    App.Console.PrintMessage(f"Bead Board v{VERSION}: {total} face(s) selected\n")

    doc = App.ActiveDocument or App.newDocument()

    doc.openTransaction("bead_board_generator: BeadBoardWall")
    try:
        obj = doc.addObject("Part::FeaturePython", "BeadBoardWall")
        BeadBoardProxy(obj)
        BeadBoardViewProxy(obj.ViewObject)
        BeadBoardProxy.set_defaults(obj)
        obj.Sources = link_sub
        obj.ViewObject.ShapeColor = (0.85, 0.82, 0.72)
        doc.recompute()
        doc.commitTransaction()
    except Exception:
        doc.abortTransaction()
        raise

    App.Console.PrintMessage(
        f"\n✓ Parametric BeadBoardWall created.\n"
        f"  Edit BeadSpacing, BeadDepth, BeadGap in the Properties panel.\n\n")


if __name__ == '__main__':
    main()
