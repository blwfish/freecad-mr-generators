"""
Parametric Shingle Generator for FreeCAD v6.0.1

Fully parametric: change ShingleWidth, Exposure, StaggerPattern, etc. in the
Properties panel and the shingles regenerate automatically.

WORKFLOW:
1. Select one or more roof faces
2. Run this macro
3. Shingle object appears — adjust properties in panel to taste

Version History:
- 6.0.1 (2026-10-07): Bug fixes (no new features, no property changes).
       * Shingles fused into one strip on 3D-print export: the auto V-groove
         chamfer (Chamfer = 0) was 1.5x MaterialThickness (0.375), larger than
         the wedge it cuts (0.25), so OCCT's makeChamfer failed and the
         failure was swallowed by a blanket `except: pass`. Auto is now 0.5x
         MaterialThickness, and a chamfer that cannot be cut (e.g. an explicit
         value >= the wedge) is reported once per recompute as a red error in
         the Report view with the cause and fix, instead of passing silently.
         Existing roofs with Chamfer = 0 pick up the groove on next recompute.
       * Fixed a misplaced block (indentation slip from the 2026-09-15
         course-math extraction) that would have silently dropped any
         starter-course shingle. Latent only: the starter course has never
         rendered (row 0 sits below the eave and is always skipped), so it is
         now parked behind shingle_geometry.ENABLE_STARTER_COURSE = False.
         Roof output is otherwise unchanged.
- 6.0.0 (2026-08-08): FeaturePython conversion — this macro previously ran a
         completely independent ~950-line implementation that never touched
         shingle_proxy.py's parametric ShingleProxy object at all (full-review
         finding freecad-mr-generators-20260808-a0b9#02): running this macro
         created static, non-parametric geometry via a legacy code path, while
         the rest of the codebase assumed shingle_generator produced the same
         kind of live Part::FeaturePython object every other generator in this
         repo does. That fork meant fixes landed on one side and not the
         other -- shingle_proxy.py was missing the ridge-sliver course-skip
         guard this macro had (v5.4.0), and this macro's own vendored face-
         coordinate-system code had a stale vertex-identity bug 5 of 6 sibling
         copies had already been fixed for (#12, #13, #14 in the same review).
         This version drops the independent pipeline entirely and matches the
         pattern every other generator's macro already uses: resolve the
         selection, create a ShingleProxy FeaturePython object, done. All
         generation logic now lives solely in shingle_proxy.py /
         shingle_geometry.py -- one implementation, not two.
       Also drops this macro's own ad-hoc one-shot spreadsheet parameter
         reader (independently duplicated shared/freecad_utils.find_spreadsheet,
         #21/#29, with a bare `except:` that silently dropped unparseable
         values, #18) in favor of FreeCAD's standard property-expression
         binding (Properties panel → right-click a property → Set expression
         → reference a spreadsheet cell) -- the same mechanism every other
         proxy in this repo already relies on for spreadsheet-driven values,
         per the f2bf0d0 refactor that intentionally left this macro as the
         one exception at the time because it wasn't proxy-based yet.
- 5.4.0 and earlier: see shingle_proxy.py's docstring and git history for the
         full changelog of the generation logic itself, which is unchanged by
         this rewrite except for the fixes listed above.
"""

import FreeCAD as App
import FreeCADGui as Gui

from shingle_proxy import ShingleProxy, ShingleViewProxy, VERSION


def main():
    sel = Gui.Selection.getSelectionEx()
    if not sel:
        App.Console.PrintError("Nothing selected — please select one or more roof faces.\n")
        return

    link_sub = []
    for sel_obj in sel:
        if not sel_obj.HasSubObjects:
            App.Console.PrintWarning(
                f"  {sel_obj.Object.Label}: select a face, not the whole object\n")
            continue
        face_names = [s for s in sel_obj.SubElementNames if s.startswith("Face")]
        if face_names:
            link_sub.append((sel_obj.Object, tuple(face_names)))

    if not link_sub:
        App.Console.PrintError("No faces in selection.\n")
        return

    total = sum(len(n) for _, n in link_sub)
    App.Console.PrintMessage(f"Shingle v{VERSION}: {total} face(s) selected\n")

    doc = App.ActiveDocument
    if not doc:
        doc = App.newDocument("ShingleProject")

    doc.openTransaction("shingle_generator: ShingleRoof")
    try:
        obj = doc.addObject("Part::FeaturePython", "ShingleRoof")
        ShingleProxy(obj)
        ShingleViewProxy(obj.ViewObject)

        ShingleProxy.set_defaults(obj)
        obj.Sources = link_sub
        obj.ViewObject.ShapeColor = (0.55, 0.35, 0.2)

        doc.recompute()
        doc.commitTransaction()
    except Exception:
        doc.abortTransaction()
        raise

    App.Console.PrintMessage(
        f"\n✓ Parametric ShingleRoof created.\n"
        f"  Edit ShingleWidth / ShingleHeight / Exposure / StaggerPattern etc. "
        f"in the Properties panel.\n\n")


if __name__ == '__main__':
    main()
