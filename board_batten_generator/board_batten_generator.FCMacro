"""
Parametric Board-and-Batten Siding Generator for FreeCAD v2.0.1

Fully parametric: change BoardWidth, BattenWidth, BoardThickness, or
BattenProjection in the Properties panel and the siding regenerates.

WORKFLOW:
1. Select one or more wall faces
2. Run this macro
3. BoardBattenWall appears — adjust properties in panel

Version History:
- 2.0.0: FeaturePython conversion — fully parametric live-update object.
         Generation logic moved to board_batten_proxy.py.
- 1.1.0: Transaction wrapping for undo
- 1.0.0: Initial release
"""

import FreeCAD as App
import FreeCADGui as Gui
import sys

from board_batten_proxy import BoardBattenProxy, BoardBattenViewProxy, VERSION


def main():
    sel = Gui.Selection.getSelectionEx()
    if not sel:
        App.Console.PrintError("Nothing selected — please select one or more wall faces.\n")
        return

    link_sub = []
    for sel_obj in sel:
        if not sel_obj.HasSubObjects:
            App.Console.PrintWarning(f"  {sel_obj.Object.Label}: select a face\n")
            continue
        face_names = [s for s in sel_obj.SubElementNames if s.startswith("Face")]
        if face_names:
            link_sub.append((sel_obj.Object, tuple(face_names)))

    if not link_sub:
        App.Console.PrintError("No faces in selection.\n")
        return

    total = sum(len(n) for _, n in link_sub)
    App.Console.PrintMessage(f"Board-and-Batten v{VERSION}: {total} face(s) selected\n")

    doc = App.ActiveDocument or App.newDocument()

    doc.openTransaction("board_batten_generator: BoardBattenWall")
    try:
        obj = doc.addObject("Part::FeaturePython", "BoardBattenWall")
        BoardBattenProxy(obj)
        BoardBattenViewProxy(obj.ViewObject)
        BoardBattenProxy.set_defaults(obj)
        obj.Sources = link_sub
        obj.ViewObject.ShapeColor = (0.85, 0.72, 0.52)
        doc.recompute()
        doc.commitTransaction()
    except Exception:
        doc.abortTransaction()
        raise

    App.Console.PrintMessage(
        f"\n✓ Parametric BoardBattenWall created.\n"
        f"  Edit BoardWidth, BattenWidth, etc. in the Properties panel.\n\n")


if __name__ == '__main__':
    main()
