"""
Parametric Brick Generator Macro v7.4.0

Fully parametric: change BondPattern, BrickWidth, MortarDepth, etc. in the
Properties panel and the brickwork regenerates automatically.

ARCHITECTURAL CHANGE from v5.x:
  Previous versions modified the source wall in-place (destructive/irreversible).
  v6.0 creates a parametric BrickedWall output object that is a modified COPY of
  the source shape.  The source wall is unchanged.
  → Hide the source wall; use the BrickedWall output for export/printing.

WORKFLOW:
1. Select one or more faces on a wall
2. Run this macro
3. BrickedWall appears — hide the original wall
4. Adjust BondPattern, BrickWidth, MortarDepth, etc. in the Properties panel

Version History:
- 6.0.0: FeaturePython conversion — fully parametric, non-destructive output.
         Generation logic moved to brick_proxy.py.
         Source wall unchanged; BrickedWall is a modified copy.
- 5.4.1: Log version on startup.
- 5.4.0: Delete dead sketch workflow; fix mortarDepth spreadsheet alias.
- 5.3.0: Transaction wrapping for undo.
- 5.2.0: Remove U snap; brick clipping at window edges.
- 5.0.0: Engraved mortar approach (pockets cut INTO wall).
"""

import FreeCAD as App
import FreeCADGui as Gui
import sys

from brick_proxy import BrickProxy, BrickViewProxy, VERSION

App.Console.PrintMessage(f"Brick Generator v{VERSION}\n")


def main():
    sel = Gui.Selection.getSelectionEx()
    if not sel:
        App.Console.PrintError(
            "Nothing selected — please select one or more faces on a wall.\n")
        return

    if not sel[0].HasSubObjects:
        App.Console.PrintError(
            "Select specific faces (not the whole object).\n"
            "Ctrl+click faces in the 3D view, then run.\n")
        return

    # BrickProxy.execute() only accepts faces from a single source object
    # (unlike some sibling generators) -- silently using only sel[0] and
    # dropping any additional selected objects gave no indication why the
    # rest of a multi-object selection was ignored (full-review finding
    # freecad-mr-generators-20260808-a0b9#25). Now this is loud instead.
    if len(sel) > 1:
        other_labels = [s.Object.Label for s in sel[1:]]
        App.Console.PrintWarning(
            f"Brick Generator: {len(sel)} objects selected, but only one "
            f"object's faces can be bricked at a time -- using "
            f"'{sel[0].Object.Label}'; ignoring face(s) on "
            f"{', '.join(other_labels)}. Run again separately for each "
            f"other object.\n")

    sel_obj = sel[0].Object
    sub_elements = [s for s in sel[0].SubElementNames if s.startswith('Face')]
    if not sub_elements:
        App.Console.PrintError("No faces in selection.\n")
        return

    App.Console.PrintMessage(
        f"Brick Generator v{VERSION}: {len(sub_elements)} face(s) on '{sel_obj.Label}'\n")

    doc = App.ActiveDocument
    if not doc:
        doc = App.newDocument("BrickProject")


    link_sub = [(sel_obj, tuple(sub_elements))]
    obj_label = sel_obj.Label

    doc.openTransaction(f"brick_generator: BrickedWall_{obj_label}")
    try:
        obj = doc.addObject("Part::FeaturePython", f"BrickedWall_{obj_label}")
        BrickProxy(obj)
        BrickViewProxy(obj.ViewObject)

        BrickProxy.set_defaults(obj)
        obj.Sources = link_sub

        # Match source color
        try:
            obj.ViewObject.ShapeColor = sel_obj.ViewObject.ShapeColor
        except Exception:
            pass

        doc.recompute()
        doc.commitTransaction()
    except Exception:
        doc.abortTransaction()
        raise

    App.Console.PrintMessage(
        f"\n✓ Parametric BrickedWall_{obj_label} created.\n"
        f"  Hide '{obj_label}' (the source wall) to see the result.\n"
        f"  Adjust BondPattern, BrickWidth, MortarDepth, etc. in Properties.\n\n")


if __name__ == '__main__':
    main()
