"""
Parametric Slate Roof Generator for FreeCAD v1.0.0

Generates flat slate tiles on selected roof faces.
Fully parametric: change tile dimensions in the Properties panel and tiles
regenerate automatically.

WORKFLOW:
1. Ctrl+click one or more roof faces
2. Run this macro
3. Adjust TileWidth, TileHeight, MaterialThickness, Exposure, StaggerPattern
   in the Properties panel — tiles update live

HO scale defaults: 2.0 × 2.5 mm tiles, 2.2 mm exposure

Requires: slate_proxy.py, slate_geometry.py in same directory
          roof_geometry.py in _lib/ subdirectory or generators/_shared/
"""

import FreeCAD as App
import FreeCADGui as Gui
import sys
import os

from slate_proxy import SlateProxy, SlateViewProxy, VERSION

GENERATOR_NAME = "slate_generator"


def main():
    sel = Gui.Selection.getSelectionEx()
    if not sel:
        App.Console.PrintError(
            "Nothing selected — Ctrl+click one or more roof faces.\n")
        return

    face_entries = []
    for sel_obj in sel:
        if not sel_obj.HasSubObjects:
            continue
        for sub in sel_obj.SubElementNames:
            if sub.startswith('Face'):
                face_entries.append((sel_obj.Object, sub))

    if not face_entries:
        App.Console.PrintError(
            "No faces selected. Select faces (not whole objects).\n")
        return

    doc = App.ActiveDocument
    if not doc:
        doc = App.newDocument("SlateProject")

    App.Console.PrintMessage(
        f"Slate Generator v{VERSION}: {len(face_entries)} face(s) selected\n")

    # Build LinkSubList grouped by object
    link_map = {}
    for obj, sub in face_entries:
        link_map.setdefault(obj, []).append(sub)
    link_sub = [(o, tuple(subs)) for o, subs in link_map.items()]

    doc.openTransaction("slate_generator: SlateTiles")
    try:
        obj = doc.addObject("Part::FeaturePython", "SlateTiles")
        SlateProxy(obj)
        SlateViewProxy(obj.ViewObject)
        SlateProxy.set_defaults(obj)
        obj.Sources = link_sub
        obj.ViewObject.ShapeColor = (0.35, 0.35, 0.40)

        doc.recompute()
        doc.commitTransaction()
    except Exception:
        doc.abortTransaction()
        raise

    App.Console.PrintMessage(
        f"\n✓ Parametric SlateTiles created.\n"
        f"  Edit TileWidth, TileHeight, etc. in the Properties panel.\n\n")


if __name__ == '__main__':
    main()
